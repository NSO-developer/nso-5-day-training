module radius_service {
  namespace "http://com/example/radius_service";
  prefix radius_service;

  import ietf-inet-types {
    prefix inet;
  }
  import tailf-ncs {
    prefix ncs;
  }

  augment /ncs:services {
  list radius_service {
    key Region;

    leaf Region {
      type enumeration {
        enum "AMER";
        enum "APJC";
        enum "EMEA";
      }
    }

    uses ncs:service-data;
    ncs:servicepoint "radius_service";

    // may replace this with other ways of refering to the devices.
    leaf-list device {
      type leafref {
        path "/ncs:devices/ncs:device/ncs:name";
      }
    }

    leaf ip-address {
      type inet:ipv4-address;
    }
  }
  } // augment /ncs:services {
  }
